// ***** MODIFIED VERSION of CadSoft's drill-aid ULP!!
// By MadWizard for imagedump script. See www.madwizard.org


string create_layer = "GRID mm;\nLAYER 116 drillImage;\nCHANGE LAYER 116;\n";
string render_layer = "SET FILL_LAYER drillImage 1;\nDISPLAY NONE drillImage;\n";
string undo_layer = "UNDO;\n";

void draw_drillhole(int x, int y, int drill) {
   real radius = u2mm(drill) / 3;
   string h;
   sprintf(h, "circle 0 (%.3f %.3f) (%.3f %.3f);\n", u2mm(x), u2mm(y), u2mm(x)+radius, u2mm(y)+radius);
   create_layer += h;
   undo_layer += "UNDO;\n";
   return;
}

if (argc < 3) {
    dlgMessageBox("Specify filename and dpi", "OK");
} else {
    render_layer += "EXPORT IMAGE " + argv[1] + " MONOCHROME " + argv[2] + ";\n";

    if (board) board(B) {
        B.holes(L) {
            draw_drillhole(L.x, L.y, L.drill);
        }
        B.elements(E) {
            E.package.holes(H) {
            draw_drillhole(H.x, H.y, H.drill);
            }
            E.package.contacts(C) {
            if (C.pad) {
                draw_drillhole(C.pad.x, C.pad.y, C.pad.drill);
            }
            }
        }
        B.signals(S) {
            S.vias(V) {
            draw_drillhole(V.x, V.y, V.drill);
            }
        }
        exit (create_layer + render_layer + undo_layer);
    } else {
        dlgMessageBox("Start this ULP in a Board!", "OK");
    }
}

exit (0);
